# uav_altitude_hold_requirements

## #1: Throttle command tracks commanded altitude (Functional)
The altitude-hold controller shall compute a throttle command that drives measured altitude toward commanded altitude.

## #2: Proportional feedback on altitude error (Functional)
The controller shall use proportional feedback on the altitude error between commanded and measured altitude.

## #3: Vertical-rate damping (Functional)
The controller shall use vertical-rate damping to reduce overshoot and oscillation around the commanded altitude.

## #4: Bounded-integral action without windup (Functional)
The controller shall use a bounded-integral term to eliminate steady-state altitude error without integrator windup.

## #5: Input validity gating (Functional)
The controller shall validate all inputs for range and validity before computing a throttle command.

## #6: Safe hover fallback on invalid input (Functional)
Upon detection of an invalid input, the controller shall command a safe 0.50 hover throttle instead of a computed command.

## #7: Output saturation and fixed-rate execution (Functional)
The controller shall limit the throttle command to the range [0.0, 1.0] and shall execute deterministically at a fixed 0.02 s rate.

## #8: Compute altitude error (Functional)
The controller shall compute altitude error as commanded altitude minus measured altitude.

## #9: Apply proportional gain Kp (Functional)
The controller shall multiply altitude error by proportional gain Kp = 0.04 to produce the proportional term.

## #10: Apply rate-damping gain Kd (Functional)
The controller shall multiply measured vertical rate by rate-damping gain Kd = -0.06 to produce the damping term.

## #11: Apply integral gain Ki (Functional)
The controller shall multiply altitude error by integral gain Ki = 0.01 before accumulation.

## #12: Accumulate integral at fixed rate (Functional)
The controller shall accumulate the integral term at the model's fixed 0.02 s sample rate.

## #13: Clamp integral term (anti-windup) (Functional)
The controller shall clamp the accumulated integral term to the range [-0.3, 0.3] to prevent windup.

## #14: Combine trim, P, D, and I terms (Functional)
The controller shall sum a fixed 0.5 hover-trim value with the proportional, damping, and integral terms to form the unsaturated throttle command.

## #15: Reject out-of-range altitude (Functional)
The controller shall reject a commanded or measured altitude that is outside the range [0, 500] meters.

## #16: Reject out-of-range vertical rate (Functional)
The controller shall reject a measured vertical rate that is outside the range [-15, 15] m/s.

## #17: Reject inputs when sensor invalid (Functional)
The controller shall reject all inputs when the sensor-valid flag is false.

## #18: Treat non-finite values as invalid (Functional)
The controller shall treat non-finite (NaN/Inf) commanded altitude, measured altitude, or vertical rate values as failing the range checks in LLR-8/LLR-9.

## #19: Select fallback vs. computed command (Functional)
The controller shall select between the computed throttle command and the fixed 0.50 fallback command using the combined validity result as the selector.

## #20: Saturate final throttle command (Functional)
The controller shall saturate the final throttle command to the range [0.0, 1.0] using a fixed upper/lower limit.
